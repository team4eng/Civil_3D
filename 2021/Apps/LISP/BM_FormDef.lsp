;;;	Load Palette Code			;

;;;	Load OpenDCL Module			;

;(command "OpenDCL")


(if (not (vl-bb-ref 'bmBlockManager))
  (vl-bb-set
    'bmBlockManager
    (dcl_project_import
      '("YWt6A41RAAC6l4kgBuKTYhMSYqsPUMDmSxkNcGpkdtYpNvp1M5XRpjDX1OzmyD7iRtpUFKtI4m2F"
"HA5sbWUdVlRpNPrf3+pU23o86+is6PGs/Xr2brYoaqreOGssjdW08TQ2dmt2EGvbL9EbRU0FBYUI"
"kJCT0wkDsDcAsMUDzRGYA7G5sAVRD41tbQzPAGtyvwimesk/cVofZbhqir1wJn5+keJ9Lin1dzoi"
"pHIDTn7jrnRV3nNIvQwWOZpQ+ler9wGT5jQ8dWio+ddrrvIXhJW9wkACLCDZK883W4gfOyNmpY7J"
"+9eFzyJUq1TPa5+b5kn+EVaruBGFb8n9DXnO+HCyEf5ma2S/+OD1b2j9b5+IDb7SjQTP+l/aYrvB"
"AK8vHXIUDdZvuiPId8B623gbXZY0pHaVbiSzyl2GuMalK0xm2HUQcyStC2Y5Z2C6KnSoHDejIqR4"
"AuGaQp36Fr3jUIbU3hPGYJ1emHBMmF6iMwuAPKrHJb6dfEB0maXN6+VInVj2pNEWIPMFh78fZCnx"
"j1hSeltm+WPmj7EJjvEetNb3OiOG0UeHcsFcniljho06Aa7/ATSOfQ7wcxFYglUiddC/Z6z6IhAR"
"xU6/Fgw0oP1XILTpXQ5gw8cmUJvEc06yfUPk5YTo3L3JfvICKahHa8ptgjF5QDSOwXpCk3Ibc7+Z"
"9NdGUvggZ5SjSkpp9IwEY4Zmv5U7gEx52PTyy3BCO5ujlr4igWRPK0N8wD++DL7RaoMXbIup9auH"
"HX/hDL2Hd/WvVZF3FYsj/fF3gGWykHoti5R6jfqI9Iyp9XcuWIYDDjGOdw4xTp0VWOalCf3+AzJO"
"y/FZ0m9SG28frJWpOlxLtq8vAqE2pHdANcFiKIsKmvaXp/qP1WZlx4766692jd86Ntss2KFmeANK"
"ZItrF7CrZjjGksApsltFceb1AeZPUcSZO438xeBJZbkAEUjyQh24EAGkSsiTSRX5ABc4EaMZUKaM"
"+mc3kwuLv1HDRHiq2Rw/iLOQxWL93p+MeSBJLbkyTc+V7sdpdaIAImHRp4EpuM25vtghiK7l4MpI"
"Q/M9z4DVg+8Xy6EURBbeCC2F0aJDt4OEv6GLz4WnbfIZsd0zMTFRJOXgqLwymSHwP66uio5qyQGH"
"saCcAJOEPmGpYAbxj5JHypdXLMQiBJx3wYNRaP341WBHshMRBYKxotA5gdPxScGPT52nDRatLdoK"
"x4paZfTTgSzPpsb6rwHkCZy1iMO5xiMgj+jJsMaYsdjJ3cPwwpaTT1a7gRRWi0DygAEPseHmUdej"
"m/rjkScx7JWqAeWg8CCbpopqNhmyC4ElYAXlh+ykOxNRaPfR6UCGeJX2NQlgmggt6ooIij0hNOG3"
"Cs9mOIH3kfdRAQzUTmh12qErpVlWgyKxQY9De7fZajbZ7wCBsoPR59TzbViDIokhk/1kNugp/ADQ"
"m8GkeSS1urFarVQ7IdCAiT0lMx/AgYDAgbzIgSiLAlvp3NmlFR4HXaxbVnUYVuAFAESJIuwFIGjG"
"71u9y3tgisvu+k+GWJL+AIIlc6WnicJ94T3ggNfWjrNUgNRQ/E2eiLPAWp4jfIiMKRMNS8PAeUg+"
"fJ1oEoZugFveZQEtHqJRtMcxvvShFeJi72k+I8AiraaXmlBckrl6i/u89dsGt7axFYI2njXRJySa"
"YW/djv+OBFcgyDH/pbXoj5c4W6kNbklUBX/BWeLmrJenXp6RdQYfunOBL5qBP75RdIZ7fxFqji7A"
"g6IQnUh/EbOJWQxkB6ymUIwRa45T0IzRd8zP3B1IBaX7lsi8C05wvTLD50mx8tqWG+H+WXoCzflV"
"hDd/ASW+oW8O3XUgR8Xdzv9HBEsMCOxJvgZ6wFUkii8AoySOWbDCj8RDV5iPvYKw8HtRa4phRZX8"
"AKblMmaSgIH8auLP0Q8FSQ3hqB5FhcazIFwtp5AE4WjhXDyne9H2rv26ossQ7+l+y6R6KEJ2XUYG"
"RC+1/W/oFgOjF6E5qgA76uxwStBomwR3NVdiS7zxjWufCTp2QbDhE59Z+yOmvFISn1unwGwyDXdY"
"lHeEBP/Ln/by74Kkg2hAhZ8wQdKNYb9ErIQegqH013KvZB/GIuhHXrQDJ750dWNZhhe/PLF2gpn6"
"Q47CfVnevuTvqLWRNCVNDLHxSTMBW4hq4WvTj8wQAFMEbb7EXz/STEZNyhhx75V1qcSXdtyJCvWh"
"RxxMtmbSj3AXU9U+RKbFU6PWr/ga9dSzCI0VW0OWH0tDaq705FVl+EFLdRNmiVTW8nPNVv8h3x0m"
"p14o65o7qPH8NRM0SyZNO/ubUiRNzVySmNNnEYjfbIZiNs0a4QREXUm8fAtqqZFjUhSXHbh5fY/n"
"SfsfUPt8+Ncr1Xe8ZMDSaLdkdTXhYyRyBFG3Zw7NtED8iUSZksbCW5yi47w0FT6xNAIQMR9bQHLZ"
"H1sQ4ZgOZ5mFHtsgVh7biF7Ex6rMVBRdss0SD+ibfb17UmUNcI/EZqhDBRM/GNEGc40NmUMJn/Sz"
"+7QHk1Rq5KH2xvtYdT/zrhqm+YNPqTzthO1JMecndbKtxCBAlcA7SzOxXPWbKgvN7umXMDr829S8"
"ThlG/uWPe79mstZrQrfiwVU+ZnOK2D71u8Uv9e6JAm0V6WMO6TDlC3ivGITkmMsk28skK5RMuOlS"
"168bfZ4YpwVcn5RM+D2qG6oBGKf1XwnDmQ3sG2UF5/O4DFBI+WONoBGDSBTeEznRxFWWjo2k6NLO"
"/bJ5DYC9PSEE4wZW9Udr2KRxBNh0lP6EbqIyvYrkzXogcFaIsLGauHAfzgHMPrF32Je7G0XSrQoj"
"n083HyONxBAoC6Pp30QKYxEsF6bsC+u86NJlS8RQexDIG0iqzpPWrguSAtSeCWWLwVAcX1AT/etW"
"ieyu/7FrZuk9VQw7eSFtEZkVorPmXOJQwCag8iZT5iD/Yuq6iZP2ofBuKxSMqw/clzmESLoWn1WW"
"Ve/MbQ/WukDABDCR7IYQW9kkb+0Gz+dPU6J/EsGFlIZbe7AlOTDGR6GG4Z7nA3xgbc6FTMa5u5Us"
"y6RU5ozQGxUF7kk3OFNHncAeoGLa8G5Q6Ul71wE4abXN3yBKmTEhsxumoW7SIlIZBGFptecgxyaw"
"BVOBa5OvIlJpdSwNz+LyfiCWaT8Q38loBi8CpeTNEYtDYg6li1KlGIsVO6BQWCodK8yEdpQLL+iI"
"er8J9k1jZAu4lDagfQE86lGrqbG1Qa+0hvREpXEEVeq1dQ9linYG4IotcFOvt7vTtjwZ2T3MtFM8"
"l+6aggsc1yrfPcxWdVdSvejRsMV/EGgfdcr8cLejTp0Ty+cBcGrnku5ICmYBcEByiP4FZ87Bvrn4"
"8Kn5fzPtYcELpmF4kgoNNb3o56T3jQXWTj0HtYRi0k1qb9b9ljORuGADmlH14ARp4P1lcdNhZHtG"
"cwrzlwrwEnLSFTLzHiEdzGTu+CxfExvYraj9gJZrgDIzM59l7YF/Izoa9sCT0pUxbTA2/b+xhhr4"
"vxJIdU5C4ODi4vIxDUunhoqOw+e3crzmZeXgSNlPSX0P7Z5SNHL8WU2KWgKNMmS1nyUoqE0Qmh7Q"
"cLkb/DgYPk1MWQcaMGhn58ZMTJ3NRkwicshlpE5KMTK6FFYfMrpNqPUmqAT/vbjWT2L30j+99n/h"
"z9I74ZhsDR1C75hZiKHO+KDneGTv6hg6RBQWOpbp/INhm0YVG8/rLy1GaDmhRyCwQWLiTE9Tmox1"
"qV31CBTu04mH9cSEQNTmFK5KfQ2tYkKPjbYtYkLVdvwhGGmMWsCEJYCG6mQBsaeJxXA9gYkBeNxT"
"eg==")
      )
    )
  )
