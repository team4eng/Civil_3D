(defun c:ESDC3DVER()
  (setq	acadverlist
	'((15.0 . "2000")
	   (15.6 . "2002")
	   (16.0 . "2004")
	   (16.1 . "2005")
	   (16.2 . "2006")
	   (17.0 . "2007")
	   (17.1 . "2008")
	   (17.2 . "2009")
	   (18.0 . "2010")
	   (18.1 . "2011")
	   (18.2 . "2012")
	   (19.0 . "2013")
	   (19.1 . "2014")
	   (20.0 . "2015")
	   (20.1 . "2016")
	   (21.0 . "2017")
	   (22.0 . "2018")
	   (23.0 . "2019")
	   (23.1 . "2020")
       (24.0 . "2021")
	  )
  )
(setq closefile nil)
(if (zerop (getvar 'dwgtitled))
(progn (princ "\nThe current drawing is unsaved."))
(progn
(setvar "cmdecho" 0)
(command "aecdwgversion")
(setq startLength (+ (vl-string-search "version " (setq AECVERSION (getvar "lastprompt"))) 9))
(setq searchString (substr AECVERSION startLength))
    (cond
        ( (vl-string-search "7, 8,"searchString)
            (promptToSave "2016")
        )
        ( (vl-string-search "7, 9," searchString)
            (promptToSave "2017")
        )
        ( (vl-string-search "8, 0," searchString)
            (promptToSave "2018")
        )
        ( (vl-string-search "8, 1," searchString)
            (promptToSave "2019")
        )
        ( (vl-string-search "8, 2," searchString)
            (promptToSave "2020")
        )
    )
        (if closefile
         (command "_.close" "Y")
        )
    )
    )
(setvar "cmdecho" 1)
  (princ)
)


(defun promptToSave ( verNumber / df)
  (setq    acadverlist
    '((15.0 . "2000")
       (15.6 . "2002")
       (16.0 . "2004")
       (16.1 . "2005")
       (16.2 . "2006")
       (17.0 . "2007")
       (17.1 . "2008")
       (17.2 . "2009")
       (18.0 . "2010")
       (18.1 . "2011")
       (18.2 . "2012")
       (19.0 . "2013")
       (19.1 . "2014")
       (20.0 . "2015")
       (20.1 . "2016")
       (21.0 . "2017")
       (22.0 . "2018")
       (23.0 . "2019")
       (23.1 . "2020")
       (24.0 . "2021")
      )
  )
(setq acadver (cdr (assoc (atof (getvar "ACADVER")) acadverlist)))
  (if (not (vl-string-search acadver verNumber))
      (progn (setq df (acet-ui-message
                   (strcat "You opened a " verNumber " Civil 3D CAD File" "\n\nDo you wish to proceed ?")
                   "Warning !!"
                   4
                            )
                    )
                (if    (equal df 6)
                    (progn (setq df (acet-ui-message "Are you sure you wish to proceed ?" "Warning !!" 4))
                (if (equal df 6)
                    (progn (setq df (acet-ui-message "Are you still sure you wish to proceed ?" "Warning !!" 4))
                      (if (not (equal df 6))
                    (setq closefile T)
                      )
                    )
                   (progn (setq closefile T))
                )
                    )
              (progn (setq closefile T))
                )
            )
     );_if
  );_defun
