(defun c:ESDDWGVER()
  (setq	acadverlist
	'((15.0 . "2000")
	   (15.6 . "2002")
	   (16.0 . "2004")
	   (16.1 . "2005")
	   (16.2 . "2006")
	   (17.0 . "2007")
	   (17.1 . "2008")
	   (17.2 . "2009")
	   (18.0 . "2010")
	   (18.1 . "2011")
	   (18.2 . "2012")
	   (19.0 . "2013")
	   (19.1 . "2014")
	   (20.0 . "2015")
	   (20.1 . "2016")
	   (21.0 . "2017")
	   (22.0 . "2018")
	   (23.0 . "2019")
	   (23.1 . "2020")
       (24.0 . "2021")
	  )
  )
  (setq closefile nil)
  (if (zerop (getvar 'dwgtitled))
    (progn (princ "\nThe current drawing is unsaved."))
    (progn (setq filever (vl-princ-to-string (LM:dwgversion (strcat (getvar 'dwgprefix) (getvar 'dwgname)))))
	   (setq acadver (cdr (assoc (atof (getvar "ACADVER")) acadverlist)))
	   (if (not (vl-string-search acadver filever))
	     (progn (setq df (acet-ui-message
			       (strcat "Drawing file of version " filever " opened in CAD Version " acadver "\n\nDo you wish to proceed ?")
			       "Warning !!"
			       4
			     )
		    )
		    (if	(equal df 6)
		      (progn (setq df (acet-ui-message "Are you sure you wish to proceed ?" "Warning !!" 4))
			     (if (equal df 6)
			       (progn (setq df (acet-ui-message "Are you still sure you wish to proceed ?" "Warning !!" 4))
				      (if (not (equal df 6))
					(setq closefile T)
				      )
			       )
			       (progn (setq closefile T))
			     )
		      )
		      (progn (setq closefile T))
		    )
	     )
	   )
	   (if closefile
	     (command "_.close")
	   )
    )
  )
  (princ)
)

(defun LM:dwgversion ( dwg / des vrs )
    (cond
        (   (not
                (and
                    (setq dwg (findfile dwg))
                    (setq des (open dwg "r"))
                )
            )
        )
        (   (wcmatch (strcase dwg t) "*`.dw[gst]")
            (setq vrs (strcase (substr (read-line des) 1 6)))
        )
        (   (wcmatch (strcase dwg t) "*`.dxf")
            (repeat 7 (read-line des))
            (setq vrs (strcase (read-line des)))
        )
    )
    (if (= 'file (type des)) (close des))
    (cdr
        (assoc vrs
           '(
                ("AC1032" . "2018-2021")
                ("AC1027" . "2013-2017")
                ("AC1024" . "2010-2012")
                ("AC1021" . "2007-2009")
                ("AC1018" . "2004-2006")
                ("AC1015" . "2000-2002")
                ("AC1014" . "Release 14")
                ("AC1012" . "Release 13")
                ("AC1009" . "Release 11/12")
                ("AC1006" . "Release 10")
                ("AC1004" . "Release 9")
                ("AC1003" . "Release 2.60")
                ("AC1002" . "Release 2.50")
                ("AC1001" . "Release 2.22")
                ("AC2.22" . "Release 2.22")
                ("AC2.21" . "Release 2.21")
                ("AC2.10" . "Release 2.10")
                ("AC1.50" . "Release 2.05")
                ("AC1.40" . "Release 1.40")
                ("AC1.2"  . "Release 1.2")
                ("MC0.0"  . "Release 1.0")
            )
        )
    )
)
