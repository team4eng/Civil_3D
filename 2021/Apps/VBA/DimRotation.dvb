Attribute VB_Name = "Module1"

Public Sub DimRotation()
Dim ESDSS As AcadSelectionSet
Dim ESDobj As AcadObject
Dim ESDent As AcadEntity
ESDrot = InputBox("Rotation in degrees", "Dimension Rotate")
ESDrot = Val(ESDrot)
ESDrot = ESDrot * 3.14159265 / 180
If ThisDrawing.SelectionSets.Count = 0 Then
  Set ESDSS = ThisDrawing.SelectionSets.Add("ESDSS")
  Else
  Set ESDSS = ThisDrawing.SelectionSets(0)
  End If
 ESDSS.Clear
 ESDSS.SelectOnScreen
 For Each ESDobj In ESDSS
  If TypeOf ESDobj Is AcadDimension Then
  ESDobj.Rotation = ESDrot
  
  End If
 Next
 

End Sub
