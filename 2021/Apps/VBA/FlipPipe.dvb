Attribute VB_Name = "ExcelFunctions"
'
' MODULE_ID {FlipPipe.bas}
' {FlipPipe.dvb}
'
'
' Christopher Fugitt PROVIDES THIS PROGRAM "AS IS" AND WITH ALL FAULTS.
' Christopher Fugitt SPECIFICALLY DISCLAIMS ANY IMPLIED WARRANTY OF
' MERCHANTABILITY OR FITNESS FOR A PARTICULAR USE. Christopher Fugitt
' DOES NOT WARRANT THAT THE OPERATION OF THE PROGRAM WILL BE
' UNINTERRUPTED OR ERROR FREE.
'
' Use, duplication, or disclosure by the U.S. Government is subject to
' restrictions set forth in FAR 52.227-19 (Commercial Computer
' Software - Restricted Rights) and DFAR 252.227-7013(c)(1)(ii)
' (Rights in Technical Data and Computer Software), as applicable.
'
 Public g_oPipeApplication As AeccPipeApplication
 Public g_oPipeDocument As AeccPipeDocument
 Public g_oPipeDatabase As AeccPipeDatabase
'
'
Option Explicit
'
' Write information about the selected pipe network to a
' spreadsheed in an instance of Excel.
'
Public Sub FlipPipe()
    Dim oAcadObject As AcadObject
    Dim oAcadObjectHandleStart As AcadObject
    Dim oAcadObjectHandleEnd As AcadObject
    Dim oPipe As AeccPipe
    Dim HandleStart As String
    Dim HandleEnd As String
    Dim dPipeStartX As Double
    Dim dPipeStartY As Double
    Dim dPipeStartZ As Double
    Dim oStructureStart As AeccStructure
    Dim dPipeEndX As Double
    Dim dPipeEndY As Double
    Dim dPipeEndZ As Double
    
    Dim oStructureEnd As AeccStructure
    Dim entbasepnt As Variant
    
    On Error Resume Next
    
    ThisDrawing.Utility.GetEntity oAcadObject, entbasepnt, "Select a pipe: "
        If (TypeOf oAcadObject Is AeccPipe) Then
            ' Yes, we have a pipe.
            Set oPipe = oAcadObject
            ' if this is the first pipe, then we need to add the headings to Excel
            
            
            
            dPipeStartX = oPipe.StartPoint.X
            dPipeStartY = oPipe.StartPoint.Y
            dPipeStartZ = oPipe.StartPoint.Z
            HandleStart = oPipe.StartStructure.Handle
            Set oAcadObjectHandleStart = ThisDrawing.HandleToObject(HandleStart)
            Set oStructureStart = oAcadObjectHandleStart
                        
            dPipeEndX = oPipe.EndPoint.X
            dPipeEndY = oPipe.EndPoint.Y
            dPipeEndZ = oPipe.EndPoint.Z
            HandleEnd = oPipe.EndStructure.Handle
            Set oAcadObjectHandleEnd = ThisDrawing.HandleToObject(HandleEnd)
            Set oStructureEnd = oAcadObjectHandleEnd
            
            oPipe.Disconnect aeccPipeStart
            oPipe.Disconnect aeccPipeEnd
            
            oPipe.StartPoint.X = dPipeEndX
            oPipe.StartPoint.Y = dPipeEndY
            oPipe.StartPoint.Z = dPipeEndZ
            
            oPipe.EndPoint.X = dPipeStartX
            oPipe.EndPoint.Y = dPipeStartY
            oPipe.EndPoint.Z = dPipeStartZ
            
            oPipe.StartPoint.X = dPipeEndX
            oPipe.StartPoint.Y = dPipeEndY
            oPipe.StartPoint.Z = dPipeEndZ
                        
            oPipe.ConnectToStructure aeccPipeStart, oStructureEnd
            oPipe.ConnectToStructure aeccPipeEnd, oStructureStart
                                    
        Else
            MsgBox "You did not select a pipe."
            Exit Sub
            
        End If
End Sub
