(defun C:SX_BLK ()
	(if (> "*" "") (setq ss (ssget "_X" (list (cons 2 "*")(cons 0 "INSERT")))))
	(if (zerop (getvar "CMDACTIVE"))
		(progn (sssetfirst ss ss)(princ "\nAll blocks selected")(princ)) ss)
)

(defun C:SX_BLKA ()
	(if (> "*" "") (setq ss (ssget "_X" (list (cons 2 "`*U#*")(cons 0 "INSERT")))))
	(if (zerop (getvar "CMDACTIVE"))
		(progn (sssetfirst ss ss)(princ "\nAll Anonymous blocks selected")(princ)) ss)
)




(defun C:SX_FELN ()
(if (> "*" "")
(setq ss (ssget "_X" '((0 . "AECC_FEATURE_LINE"))))
)
(if (zerop (getvar "CMDACTIVE"))
(progn (sssetfirst ss ss)
(princ "\nAll Feature Lines selected")
(princ)
)
ss
)
)

(defun C:SX_SVFG ()
(if (> "*" "")
(setq ss (ssget "_X" '((0 . "AECC_SVFIGURE"))))
)
(if (zerop (getvar "CMDACTIVE"))
(progn (sssetfirst ss ss)
(princ "\nAll Survey Figures selected")
(princ)
)
ss
)
)



(defun C:SX_3DPL ()
(if (> "*" "")
(setq ss (ssget "_X" '((0 . "POLYLINE"))))
)
(if (zerop (getvar "CMDACTIVE"))
(progn (sssetfirst ss ss)
(princ "\nAll 3D Polylines selected")
(princ)
)
ss
)
)

(defun C:SX_POLY ()
(if (> "*" "")
(setq ss (ssget "_X" '((0 . "LWPOLYLINE"))))
)
(if (zerop (getvar "CMDACTIVE"))
(progn (sssetfirst ss ss)
(princ "\nAll Polylines selected")
(princ)
)
ss
)
)


(defun C:SX_COGO ()
(if (> "*" "")
(setq ss (ssget "_X" '((0 . "AECC_COGO_POINT"))))
)
(if (zerop (getvar "CMDACTIVE"))
(progn (sssetfirst ss ss)
(princ "\nAll Cogo Points selected")
(princ)
)
ss
)
)

(defun C:SX_LINE ()
(if (> "*" "")
(setq ss (ssget "_X" '((0 . "LINE"))))
)
(if (zerop (getvar "CMDACTIVE"))
(progn (sssetfirst ss ss)
(princ "\nAll Lines Selected")
(princ)
)
ss
)
)

(defun C:SX_ARCS ()
(if (> "*" "")
(setq ss (ssget "_X" '((0 . "ARC"))))
)
(if (zerop (getvar "CMDACTIVE"))
(progn (sssetfirst ss ss)
(princ "\nAll Arcs Selected")
(princ)
)
ss
)
)

(defun C:SX_ELPS ()
(if (> "*" "")
(setq ss (ssget "_X" '((0 . "ELLIPSE"))))
)
(if (zerop (getvar "CMDACTIVE"))
(progn (sssetfirst ss ss)
(princ "\nAll Ellipses selected")
(princ)
)
ss
)
)

(defun C:SX_SPLN ()
(if (> "*" "")
(setq ss (ssget "_X" '((0 . "SPLINE"))))
)
(if (zerop (getvar "CMDACTIVE"))
(progn (sssetfirst ss ss)
(princ "\nAll Splines selected")
(princ)
)
ss
)
)

(defun C:SX_TEXT ()
(if (> "*" "")
(setq ss (ssget "_X" '((0 . "TEXT"))))
)
(if (zerop (getvar "CMDACTIVE"))
(progn (sssetfirst ss ss)
(princ "\nAll Texts selected")
(princ)
)
ss
)
)

(defun C:SX_MTXT ()
(if (> "*" "")
(setq ss (ssget "_X" '((0 . "MTEXT"))))
)
(if (zerop (getvar "CMDACTIVE"))
(progn (sssetfirst ss ss)
(princ "\nAll Mtexts selected")
(princ)
)
ss
)
)

(defun C:SX_MLDR ()
(if (> "*" "")
(setq ss (ssget "_X" '((0 . "MULTILEADER"))))
)
(if (zerop (getvar "CMDACTIVE"))
(progn (sssetfirst ss ss)
(princ "\nAll Multileaders selected")
(princ)
)
ss
)
)

(defun C:SX_DIMM ()
(if (> "*" "")
(setq ss (ssget "_X" '((0 . "DIMENSION"))))
)
(if (zerop (getvar "CMDACTIVE"))
(progn (sssetfirst ss ss)
(princ "\nAll Dimensions selected")
(princ)
)
ss
)
)
