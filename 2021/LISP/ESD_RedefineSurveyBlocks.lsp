(defun c:ReDefVBLK ( / *error* oc spc doc block b )
  (vl-load-com)
  ;; © Lee Mac 2010

  ;; Full filename needed if block is not in the support path
  (setq BlocksToRedefine
   '(
     "C:/Autodesk/Civil_3D/2019/Block/B-Geotechnical/BORE_TTHL.dwg"
     "C:/Autodesk/Civil_3D/2019/Block/B-Geotechnical/BORE_TPIT.dwg"
	 "C:/Autodesk/Civil_3D/2019/Block/V-Survey/V-Audio-TV/CATV_CLIP_E.dwg"
	 "C:/Autodesk/Civil_3D/2019/Block/V-Survey/V-Audio-TV/CATV_JBOX_E.dwg"
	 "C:/Autodesk/Civil_3D/2019/Block/V-Survey/V-Audio-TV/CATV_MANH_E.dwg"
	 "C:/Autodesk/Civil_3D/2019/Block/V-Survey/V-Audio-TV/CATV_MRKR_E.dwg"
	 "C:/Autodesk/Civil_3D/2019/Block/V-Survey/V-Audio-TV/CATV_VALT_E.dwg"
	 "C:/Autodesk/Civil_3D/2019/Block/V-Survey/V-Communication/COMM_CLIP_E.dwg"
	 "C:/Autodesk/Civil_3D/2019/Block/V-Survey/V-Communication/COMM_JBOX_E.dwg"
	 "C:/Autodesk/Civil_3D/2019/Block/V-Survey/V-Communication/COMM_MANH_E.dwg"
	 "C:/Autodesk/Civil_3D/2019/Block/V-Survey/V-Communication/COMM_MRKR_E.dwg"
	 "C:/Autodesk/Civil_3D/2019/Block/V-Survey/V-Communication/COMM_PED_E.dwg"
	 "C:/Autodesk/Civil_3D/2019/Block/V-Survey/V-Communication/COMM_POLE_E.dwg"
	 "C:/Autodesk/Civil_3D/2019/Block/V-Survey/V-Communication/COMM_VALT_E.dwg"
	 "C:/Autodesk/Civil_3D/2019/Block/V-Survey/V-Chilled-Water/CWTR_CLIP_E.dwg"
	 "C:/Autodesk/Civil_3D/2019/Block/V-Survey/V-Chilled-Water/CWTR_MANH_E.dwg"	 
	 "C:/Autodesk/Civil_3D/2019/Block/V-Survey/V-Chilled-Water/CWTR_MRKR_E.dwg"
	 "C:/Autodesk/Civil_3D/2019/Block/V-Survey/V-Chilled-Water/CWTR_VALT_E.dwg"
	 "C:/Autodesk/Civil_3D/2019/Block/V-Survey/V-Chilled-Water/CWTR_VALV_E.dwg"
	 "C:/Autodesk/Civil_3D/2019/Block/V-Survey/V-Electric/ELEC_CABN_E.dwg"
	 "C:/Autodesk/Civil_3D/2019/Block/V-Survey/V-Electric/ELEC_CLIP_E.dwg"
	 "C:/Autodesk/Civil_3D/2019/Block/V-Survey/V-Electric/ELEC_DGUY_E.dwg"
	 "C:/Autodesk/Civil_3D/2019/Block/V-Survey/V-Electric/ELEC_HAND_E.dwg"
	 "C:/Autodesk/Civil_3D/2019/Block/V-Survey/V-Electric/ELEC_JBOX_E.dwg"
	 "C:/Autodesk/Civil_3D/2019/Block/V-Survey/V-Electric/ELEC_LGHT_E.dwg"
	 "C:/Autodesk/Civil_3D/2019/Block/V-Survey/V-Electric/ELEC_LGTB_E.dwg"
	 "C:/Autodesk/Civil_3D/2019/Block/V-Survey/V-Electric/ELEC_LGTE_E.dwg"
	 "C:/Autodesk/Civil_3D/2019/Block/V-Survey/V-Electric/ELEC_MANH_E.dwg"
	 "C:/Autodesk/Civil_3D/2019/Block/V-Survey/V-Electric/ELEC_METR_E.dwg"
	 "C:/Autodesk/Civil_3D/2019/Block/V-Survey/V-Electric/ELEC_MRKR_E.dwg"
	 "C:/Autodesk/Civil_3D/2019/Block/V-Survey/V-Electric/ELEC_PBOX_E.dwg"
	 "C:/Autodesk/Civil_3D/2019/Block/V-Survey/V-Electric/ELEC_POLE_E.dwg"
	 "C:/Autodesk/Civil_3D/2019/Block/V-Survey/V-Electric/ELEC_TOWR_E.dwg"
	 "C:/Autodesk/Civil_3D/2019/Block/V-Survey/V-Electric/ELEC_VALT_E.dwg"
	 "C:/Autodesk/Civil_3D/2019/Block/V-Survey/V-Fiber-Optic/FIBR_CLIP_E.dwg"
	 "C:/Autodesk/Civil_3D/2019/Block/V-Survey/V-Fiber-Optic/FIBR_JBOX_E.dwg"
	 "C:/Autodesk/Civil_3D/2019/Block/V-Survey/V-Fiber-Optic/FIBR_MANH_E.dwg"
	 "C:/Autodesk/Civil_3D/2019/Block/V-Survey/V-Fiber-Optic/FIBR_MRKR_E.dwg"
	 "C:/Autodesk/Civil_3D/2019/Block/V-Survey/V-Fiber-Optic/FIBR_VALT_E.dwg"
	 "C:/Autodesk/Civil_3D/2019/Block/V-Survey/V-Irrigation/IRRG_CVLV_E.dwg"
	 "C:/Autodesk/Civil_3D/2019/Block/V-Survey/V-Irrigation/IRRG_CBOX_E.dwg"
	 "C:/Autodesk/Civil_3D/2019/Block/V-Survey/V-Irrigation/IRRG_HBIB_E.dwg"
	 "C:/Autodesk/Civil_3D/2019/Block/V-Survey/V-Irrigation/IRRG_METR_E.dwg"
	 "C:/Autodesk/Civil_3D/2019/Block/V-Survey/V-Irrigation/IRRG_MRKR_E.dwg"
	 "C:/Autodesk/Civil_3D/2019/Block/V-Survey/V-Irrigation/IRRG_SPCV_E.dwg"
	 "C:/Autodesk/Civil_3D/2019/Block/V-Survey/V-Irrigation/IRRG_SPHD_E.dwg"	
	 "C:/Autodesk/Civil_3D/2019/Block/V-Survey/V-Natural-Gas/NGAS_CLIP_E.dwg"
	 "C:/Autodesk/Civil_3D/2019/Block/V-Survey/V-Natural-Gas/NGAS_LGHT_E.dwg"
	 "C:/Autodesk/Civil_3D/2019/Block/V-Survey/V-Natural-Gas/NGAS_MANH_E.dwg"
	 "C:/Autodesk/Civil_3D/2019/Block/V-Survey/V-Natural-Gas/NGAS_METR_E.dwg"
	 "C:/Autodesk/Civil_3D/2019/Block/V-Survey/V-Natural-Gas/NGAS_MRKR_E.dwg"
	 "C:/Autodesk/Civil_3D/2019/Block/V-Survey/V-Natural-Gas/NGAS_SCON_E.dwg"
	 "C:/Autodesk/Civil_3D/2019/Block/V-Survey/V-Natural-Gas/NGAS_VALT_E.dwg"
	 "C:/Autodesk/Civil_3D/2019/Block/V-Survey/V-Natural-Gas/NGAS_VALV_E.dwg"
	 "C:/Autodesk/Civil_3D/2019/Block/V-Survey/V-Natural-Gas/NGAS_VENT_E.dwg"	 
	 "C:/Autodesk/Civil_3D/2019/Block/V-Survey/V-Reclaimed-Water/NPWR_CLIP_E.dwg"
	 "C:/Autodesk/Civil_3D/2019/Block/V-Survey/V-Reclaimed-Water/NPWR_MANH_E.dwg"
	 "C:/Autodesk/Civil_3D/2019/Block/V-Survey/V-Reclaimed-Water/NPWR_METR_E.dwg"
	 "C:/Autodesk/Civil_3D/2019/Block/V-Survey/V-Reclaimed-Water/NPWR_MRKR_E.dwg"
	 "C:/Autodesk/Civil_3D/2019/Block/V-Survey/V-Reclaimed-Water/NPWR_VALT_E.dwg"
	 "C:/Autodesk/Civil_3D/2019/Block/V-Survey/V-Reclaimed-Water/NPWR_VALV_E.dwg"	
	 "C:/Autodesk/Civil_3D/2019/Block/V-Survey/V-Petroleum/PETR_CLIP_E.dwg"	 
	 "C:/Autodesk/Civil_3D/2019/Block/V-Survey/V-Petroleum/PETR_METR_E.dwg"
	 "C:/Autodesk/Civil_3D/2019/Block/V-Survey/V-Petroleum/PETR_MRKR_E.dwg"
	 "C:/Autodesk/Civil_3D/2019/Block/V-Survey/V-Petroleum/PETR_VALV_E.dwg"
	 "C:/Autodesk/Civil_3D/2019/Block/V-Survey/V-Site/PLNT_LGHT_E.dwg"
	 "C:/Autodesk/Civil_3D/2019/Block/V-Survey/V-Site/PLNT_SHRB_E.dwg"
	 "C:/Autodesk/Civil_3D/2019/Block/V-Survey/V-Site/PLNT_TREE_E.dwg"
	 "C:/Autodesk/Civil_3D/2019/Block/V-Survey/V-Site/PLNT_TREH_E.dwg"	 
	 "C:/Autodesk/Civil_3D/2019/Block/V-Survey/V-Site/RAIL_SIGN_E.dwg"	 
	 "C:/Autodesk/Civil_3D/2019/Block/V-Survey/V-Site/SITE_BKRK_E.dwg"
	 "C:/Autodesk/Civil_3D/2019/Block/V-Survey/V-Site/SITE_BLRD_E.dwg"
	 "C:/Autodesk/Civil_3D/2019/Block/V-Survey/V-Site/SITE_BNCH_E.dwg"
	 "C:/Autodesk/Civil_3D/2019/Block/V-Survey/V-Site/SITE_BUS_E.dwg"
	 "C:/Autodesk/Civil_3D/2019/Block/V-Survey/V-Site/SITE_GCAN_E.dwg"
	 "C:/Autodesk/Civil_3D/2019/Block/V-Survey/V-Site/SITE_GRPT_E.dwg"
	 "C:/Autodesk/Civil_3D/2019/Block/V-Survey/V-Site/SITE_MAIL_E.dwg"
	 "C:/Autodesk/Civil_3D/2019/Block/V-Survey/V-Site/SITE_MANH_E.dwg"
	 "C:/Autodesk/Civil_3D/2019/Block/V-Survey/V-Site/SITE_PMTR_E.dwg"
	 "C:/Autodesk/Civil_3D/2019/Block/V-Survey/V-Site/SITE_POST_E.dwg"
	 "C:/Autodesk/Civil_3D/2019/Block/V-Survey/V-Site/SITE_SIGN_E.dwg"
     "C:/Autodesk/Civil_3D/2019/Block/V-Survey/V-Site/SITE_VALT_E.dwg"		 
	 "C:/Autodesk/Civil_3D/2019/Block/V-Survey/V-Storm-Drain/STRM_AINL_E.dwg"
	 "C:/Autodesk/Civil_3D/2019/Block/V-Survey/V-Storm-Drain/STRM_ARRW_E.dwg"
	 "C:/Autodesk/Civil_3D/2019/Block/V-Survey/V-Storm-Drain/STRM_CINL_E.dwg"
	 "C:/Autodesk/Civil_3D/2019/Block/V-Survey/V-Storm-Drain/STRM_CLIP_E.dwg"
	 "C:/Autodesk/Civil_3D/2019/Block/V-Survey/V-Storm-Drain/STRM_COUT_E.dwg"
	 "C:/Autodesk/Civil_3D/2019/Block/V-Survey/V-Storm-Drain/STRM_COVR_E.dwg"
	 "C:/Autodesk/Civil_3D/2019/Block/V-Survey/V-Storm-Drain/STRM_GINL_E.dwg"
	 "C:/Autodesk/Civil_3D/2019/Block/V-Survey/V-Storm-Drain/STRM_HEAD_E.dwg"
	 "C:/Autodesk/Civil_3D/2019/Block/V-Survey/V-Storm-Drain/STRM_MANH_E.dwg"
	 "C:/Autodesk/Civil_3D/2019/Block/V-Survey/V-Storm-Drain/STRM_MRKR_E.dwg"
	 "C:/Autodesk/Civil_3D/2019/Block/V-Survey/V-Storm-Drain/STRM_RFDR_E.dwg"
	 "C:/Autodesk/Civil_3D/2019/Block/V-Survey/V-Storm-Drain/STRM_VALT_E.dwg"
	 "C:/Autodesk/Civil_3D/2019/Block/V-Survey/V-Storm-Drain/STRM_WNGW_E.dwg"	 
	 "C:/Autodesk/Civil_3D/2019/Block/V-Survey/V-Traffic-Signal/TRAF_CBOX_E.dwg"
	 "C:/Autodesk/Civil_3D/2019/Block/V-Survey/V-Traffic-Signal/TRAF_CLIP_E.dwg"
	 "C:/Autodesk/Civil_3D/2019/Block/V-Survey/V-Traffic-Signal/TRAF_LGHT_E.dwg"
	 "C:/Autodesk/Civil_3D/2019/Block/V-Survey/V-Traffic-Signal/TRAF_MANH_E.dwg"
	 "C:/Autodesk/Civil_3D/2019/Block/V-Survey/V-Traffic-Signal/TRAF_MRKR_E.dwg"
	 "C:/Autodesk/Civil_3D/2019/Block/V-Survey/V-Traffic-Signal/TRAF_PBOX_E.dwg"
	 "C:/Autodesk/Civil_3D/2019/Block/V-Survey/V-Traffic-Signal/TRAF_PEDS_E.dwg"
	 "C:/Autodesk/Civil_3D/2019/Block/V-Survey/V-Traffic-Signal/TRAF_SGNE_E.dwg"
	 "C:/Autodesk/Civil_3D/2019/Block/V-Survey/V-Traffic-Signal/TRAF_SIGN_E.dwg"
	 "C:/Autodesk/Civil_3D/2019/Block/V-Survey/V-Traffic-Signal/TRAF_VALT_E.dwg"
	 "C:/Autodesk/Civil_3D/2019/Block/V-Survey/V-Water/WATR_45_E.dwg"
	 "C:/Autodesk/Civil_3D/2019/Block/V-Survey/V-Water/WATR_45L_E.dwg"
	 "C:/Autodesk/Civil_3D/2019/Block/V-Survey/V-Water/WATR_45R_E.dwg"
	 "C:/Autodesk/Civil_3D/2019/Block/V-Survey/V-Water/WATR_90_E.dwg"
	 "C:/Autodesk/Civil_3D/2019/Block/V-Survey/V-Water/WATR_225_E.dwg"
	 "C:/Autodesk/Civil_3D/2019/Block/V-Survey/V-Water/WATR_1125_E.dwg"
	 "C:/Autodesk/Civil_3D/2019/Block/V-Survey/V-Water/WATR_5625_E.dwg"
	 "C:/Autodesk/Civil_3D/2019/Block/V-Survey/V-Water/WATR_AFV_E.dwg"
	 "C:/Autodesk/Civil_3D/2019/Block/V-Survey/V-Water/WATR_ARV_E.dwg"
	 "C:/Autodesk/Civil_3D/2019/Block/V-Survey/V-Water/WATR_ARVC_E.dwg"
	 "C:/Autodesk/Civil_3D/2019/Block/V-Survey/V-Water/WATR_ARVM_E.dwg"
	 "C:/Autodesk/Civil_3D/2019/Block/V-Survey/V-Water/WATR_BFPV_E.dwg"
	 "C:/Autodesk/Civil_3D/2019/Block/V-Survey/V-Water/WATR_BVLV_E.dwg"
	 "C:/Autodesk/Civil_3D/2019/Block/V-Survey/V-Water/WATR_CAP_E.dwg"
	 "C:/Autodesk/Civil_3D/2019/Block/V-Survey/V-Water/WATR_CKDV_E.dwg"
	 "C:/Autodesk/Civil_3D/2019/Block/V-Survey/V-Water/WATR_CKSV_E.dwg"
	 "C:/Autodesk/Civil_3D/2019/Block/V-Survey/V-Water/WATR_CLIP_E.dwg"
	 "C:/Autodesk/Civil_3D/2019/Block/V-Survey/V-Water/WATR_COPL_E.dwg"
	 "C:/Autodesk/Civil_3D/2019/Block/V-Survey/V-Water/WATR_CROS_E.dwg"
	 "C:/Autodesk/Civil_3D/2019/Block/V-Survey/V-Water/WATR_DRMH_E.dwg"
	 "C:/Autodesk/Civil_3D/2019/Block/V-Survey/V-Water/WATR_DVLV_E.dwg"
	 "C:/Autodesk/Civil_3D/2019/Block/V-Survey/V-Water/WATR_FCON_E.dwg"
	 "C:/Autodesk/Civil_3D/2019/Block/V-Survey/V-Water/WATR_FHYD_E.dwg"
	 "C:/Autodesk/Civil_3D/2019/Block/V-Survey/V-Water/WATR_FMTR_E.dwg"
	 "C:/Autodesk/Civil_3D/2019/Block/V-Survey/V-Water/WATR_HAND_E.dwg"
	 "C:/Autodesk/Civil_3D/2019/Block/V-Survey/V-Water/WATR_HPRV_E.dwg"
	 "C:/Autodesk/Civil_3D/2019/Block/V-Survey/V-Water/WATR_MANH_E.dwg"
	 "C:/Autodesk/Civil_3D/2019/Block/V-Survey/V-Water/WATR_MATC_E.dwg"
	 "C:/Autodesk/Civil_3D/2019/Block/V-Survey/V-Water/WATR_METR_E.dwg"
	 "C:/Autodesk/Civil_3D/2019/Block/V-Survey/V-Water/WATR_MRKR_E.dwg"
	 "C:/Autodesk/Civil_3D/2019/Block/V-Survey/V-Water/WATR_MWEL_E.dwg"
	 "C:/Autodesk/Civil_3D/2019/Block/V-Survey/V-Water/WATR_PLUG_E.dwg"
	 "C:/Autodesk/Civil_3D/2019/Block/V-Survey/V-Water/WATR_PRJS_E.dwg"
	 "C:/Autodesk/Civil_3D/2019/Block/V-Survey/V-Water/WATR_PRV_E.dwg"
	 "C:/Autodesk/Civil_3D/2019/Block/V-Survey/V-Water/WATR_PSV_E.dwg"
	 "C:/Autodesk/Civil_3D/2019/Block/V-Survey/V-Water/WATR_REDC_E.dwg"
	 "C:/Autodesk/Civil_3D/2019/Block/V-Survey/V-Water/WATR_SCON_E.dwg"
	 "C:/Autodesk/Civil_3D/2019/Block/V-Survey/V-Water/WATR_SVLV_E.dwg"
	 "C:/Autodesk/Civil_3D/2019/Block/V-Survey/V-Water/WATR_TEE_E.dwg"
	 "C:/Autodesk/Civil_3D/2019/Block/V-Survey/V-Water/WATR_VALV_E.dwg"
	 "C:/Autodesk/Civil_3D/2019/Block/V-Survey/V-Water/WATR_VALT_E.dwg"
	 "C:/Autodesk/Civil_3D/2019/Block/V-Survey/V-Water/WATR_VENT_E.dwg"
	 "C:/Autodesk/Civil_3D/2019/Block/V-Survey/V-Water/WATR_VRV_E.dwg"
	 "C:/Autodesk/Civil_3D/2019/Block/V-Survey/V-Water/WATR_WELL_E.dwg"
	 "C:/Autodesk/Civil_3D/2019/Block/V-Survey/V-WasteWater/WWTR_ARV_E.dwg"	 
	 "C:/Autodesk/Civil_3D/2019/Block/V-Survey/V-WasteWater/WWTR_BFPV_E.dwg"	 
	 "C:/Autodesk/Civil_3D/2019/Block/V-Survey/V-WasteWater/WWTR_CAP_E.dwg"
	 "C:/Autodesk/Civil_3D/2019/Block/V-Survey/V-WasteWater/WWTR_CLIP_E.dwg"
	 "C:/Autodesk/Civil_3D/2019/Block/V-Survey/V-WasteWater/WWTR_COUT_E.dwg"
	 "C:/Autodesk/Civil_3D/2019/Block/V-Survey/V-WasteWater/WWTR_FMTR_E.dwg"
     "C:/Autodesk/Civil_3D/2019/Block/V-Survey/V-WasteWater/WWTR_LSTA_E.dwg"	 	 
	 "C:/Autodesk/Civil_3D/2019/Block/V-Survey/V-WasteWater/WWTR_MANH_E.dwg"
	 "C:/Autodesk/Civil_3D/2019/Block/V-Survey/V-WasteWater/WWTR_METR_E.dwg"
	 "C:/Autodesk/Civil_3D/2019/Block/V-Survey/V-WasteWater/WWTR_MRKR_E.dwg"
	 "C:/Autodesk/Civil_3D/2019/Block/V-Survey/V-WasteWater/WWTR_PLUG_E.dwg"	 
	 "C:/Autodesk/Civil_3D/2019/Block/V-Survey/V-WasteWater/WWTR_PRJS_E.dwg"
     "C:/Autodesk/Civil_3D/2019/Block/V-Survey/V-WasteWater/WWTR_REDC_E.dwg"	 	 
	 "C:/Autodesk/Civil_3D/2019/Block/V-Survey/V-WasteWater/WWTR_SCON_E.dwg"
	 "C:/Autodesk/Civil_3D/2019/Block/V-Survey/V-WasteWater/WWTR_VALT_E.dwg"
	 "C:/Autodesk/Civil_3D/2019/Block/V-Survey/V-WasteWater/WWTR_VALV_E.dwg"
	 "C:/Autodesk/Civil_3D/2019/Block/V-Survey/V-WasteWater/WWTR_VENT_E.dwg"
	 "C:/Autodesk/Civil_3D/2019/Block/V-Survey/V-Control-Property/SURV_BDF.dwg"
     "C:/Autodesk/Civil_3D/2019/Block/V-Survey/V-Control-Property/SURV_BDS.dwg"
     "C:/Autodesk/Civil_3D/2019/Block/V-Survey/V-Control-Property/SURV_BF.dwg"
     "C:/Autodesk/Civil_3D/2019/Block/V-Survey/V-Control-Property/SURV_BMF.dwg"
     "C:/Autodesk/Civil_3D/2019/Block/V-Survey/V-Control-Property/SURV_BMS.dwg"
     "C:/Autodesk/Civil_3D/2019/Block/V-Survey/V-Control-Property/SURV_BS.dwg"
     "C:/Autodesk/Civil_3D/2019/Block/V-Survey/V-Control-Property/SURV_CP.dwg"
     "C:/Autodesk/Civil_3D/2019/Block/V-Survey/V-Control-Property/SURV_CPF.dwg"
     "C:/Autodesk/Civil_3D/2019/Block/V-Survey/V-Control-Property/SURV_CPS.dwg"
     "C:/Autodesk/Civil_3D/2019/Block/V-Survey/V-Control-Property/SURV_CSF.dwg"
     "C:/Autodesk/Civil_3D/2019/Block/V-Survey/V-Control-Property/SURV_CSS.dwg"
     "C:/Autodesk/Civil_3D/2019/Block/V-Survey/V-Control-Property/SURV_DHF.dwg"
     "C:/Autodesk/Civil_3D/2019/Block/V-Survey/V-Control-Property/SURV_DHS.dwg"
     "C:/Autodesk/Civil_3D/2019/Block/V-Survey/V-Control-Property/SURV_HTF.dwg"
     "C:/Autodesk/Civil_3D/2019/Block/V-Survey/V-Control-Property/SURV_HTS.dwg"
     "C:/Autodesk/Civil_3D/2019/Block/V-Survey/V-Control-Property/SURV_IPF.dwg"
     "C:/Autodesk/Civil_3D/2019/Block/V-Survey/V-Control-Property/SURV_IPS.dwg"
     "C:/Autodesk/Civil_3D/2019/Block/V-Survey/V-Control-Property/SURV_IRF.dwg"
     "C:/Autodesk/Civil_3D/2019/Block/V-Survey/V-Control-Property/SURV_IRS.dwg"
     "C:/Autodesk/Civil_3D/2019/Block/V-Survey/V-Control-Property/SURV_MF.dwg"
     "C:/Autodesk/Civil_3D/2019/Block/V-Survey/V-Control-Property/SURV_MNF.dwg"
     "C:/Autodesk/Civil_3D/2019/Block/V-Survey/V-Control-Property/SURV_MNS.dwg"
     "C:/Autodesk/Civil_3D/2019/Block/V-Survey/V-Control-Property/SURV_MS.dwg"
	 "C:/Autodesk/Civil_3D/2019/Block/V-Survey/V-Control-Property/SURV_NF.dwg"
	 "C:/Autodesk/Civil_3D/2019/Block/V-Survey/V-Control-Property/SURV_NS.dwg"
	 "C:/Autodesk/Civil_3D/2019/Block/V-Survey/V-Control-Property/SURV_PPF.dwg"
	 "C:/Autodesk/Civil_3D/2019/Block/V-Survey/V-Control-Property/SURV_PPS.dwg"
     "C:/Autodesk/Civil_3D/2019/Block/V-Survey/V-Control-Property/SURV_TBF.dwg"
     "C:/Autodesk/Civil_3D/2019/Block/V-Survey/V-Control-Property/SURV_TBS.dwg"
	 "C:/Autodesk/Civil_3D/2019/Block/V-Survey/V-Control-Property/SURV_TRV.dwg"
     "C:/Autodesk/Civil_3D/2019/Block/V-Survey/V-Control-Property/SURV_XF.dwg"
     "C:/Autodesk/Civil_3D/2019/Block/V-Survey/V-Control-Property/SURV_XS.dwg"
	 "C:/Autodesk/Civil_3D/2019/Block/V-Survey/TICK_TOPO_CUT.dwg"
	 "C:/Autodesk/Civil_3D/2019/Block/V-Survey/TICK_TOPO_FILL.dwg"
    )
  )

  (defun *error* ( msg )
    (and oc (setvar 'CMDECHO oc))
    (or (wcmatch (strcase msg) "*BREAK,*CANCEL*,*EXIT*")
        (princ (strcat "\n** Error: " msg " **")))
    (princ)
  )

  (setq spc
    (vlax-get (vla-get-ActiveDocument (vlax-get-acad-object))
      (if (= 1 (getvar 'CVPORT)) 'PaperSpace 'ModelSpace)
    )
  )
  
  (setq oc (getvar 'CMDECHO)) (setvar 'CMDECHO 0)

  (foreach block BlocksToRedefine
    (if (setq b (findfile (strcat block (if (not (vl-filename-extension block)) ".dwg" ""))))
      (progn
        (vla-delete
          (vla-insertblock spc
            (vlax-3D-point '(0. 0. 0.)) b 1. 1. 1. 0.
          )
        )
        (vl-cmdf "_.attsync" "_N" (vl-filename-base b))
      )
      (princ (strcat "\n** Cannot Find Block: " block " **"))
    )
  )
  
  (setvar 'CMDECHO oc)
  (princ)
)
