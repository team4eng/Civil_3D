(defun c:BLK_Flip ( / SelSet Counter EntName Obj )
  (princ "Command: Rotate selected Blocks 180 degrees " )
  (if (setq SelSet (ssget '((0 . "INSERT" ))) )
    (progn
      (setq Counter 0 )
      (vl-load-com)
      (while (setq EntName (ssname SelSet Counter ))
        (setq Obj (vlax-ename->vla-Object EntName ) )
        (vlax-put-property Obj "Rotation" (+ (vlax-get Obj "Rotation" ) pi ) )
        (vlax-release-Object Obj )
        (setq Counter (1+ Counter ) )
      )
    )
    (princ ". . no Block selected ! " )
  )
  (princ)
)
