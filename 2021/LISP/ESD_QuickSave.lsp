(defun c:QAS ()
 (command ".audit" "yes")
 (command ".qsave")
 (princ)
)

(defun c:QASC ()
 (command ".audit" "yes")
 (command ".qsave")
 (command "_CLOSE" "_Y")
 (princ)
)


(defun c:QwS () 
 (command "-purge" "all" "*" "N")
 (command ".audit" "yes")
 (command ".qsave")
 (princ)
)

(defun c:QwSC () 
 (command "-purge" "all" "*" "N")
 (command ".audit" "yes")
 (command ".qsave")
 (command "_CLOSE" "_Y")
 (princ)
)

(defun C:QASA (/ $acad docs dnum this)
  (vl-load-com)
  (setq	$acad (vlax-get-acad-object)
	docs  (vla-get-Documents $acad)
	this  (vla-get-ActiveDocument $acad)
	dnum  (vla-get-count docs)
  )
  (vlax-for each docs
    (vla-AuditInfo each T)
    (vla-save each)
  )
  (vlax-release-object docs)
  (vlax-release-object this)
  (vlax-release-object $acad)
  (princ (strcat "\nProcessed " (itoa dnum) " drawings. "))
  (princ)
)

(defun C:QWSA (/ $acad docs dnum this)
  (vl-load-com)
  (setq	$acad (vlax-get-acad-object)
	docs  (vla-get-Documents $acad)
	this  (vla-get-ActiveDocument $acad)
	dnum  (vla-get-count docs)
  )
  (vlax-for each docs
    (vla-purgeall each)
    (vla-AuditInfo each T)
    (vla-save each)
  )
  (vlax-release-object docs)
  (vlax-release-object this)
  (vlax-release-object $acad)
  (princ (strcat "\nProcessed " (itoa dnum) " drawings. "))
  (princ)
)
