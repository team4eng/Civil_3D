(defun c:chd ( / disp drafting)
  (setvar "cmdecho" 1)
  (princ "\nLoading Menu...")
  (initget 1 "BLACK WHITE GREY")
  (setq MYCOLOR (getkword "\nChoose [BLACK/WHITE/GREY]: "))
  (cond
	( (= MYCOLOR "BLACK") 
	(vl-load-com)
	(setenv "2D Model viewport control color" "16777215")
  	(setq disp (vla-get-display (vla-get-preferences (vlax-get-acad-object))))
  	(setq drafting (vla-get-drafting (vla-get-preferences (vlax-get-acad-object))))
  	(vla-put-GraphicsWinModelBackgrndColor disp 0)
  	(vla-put-GraphicsWinLayoutBackgrndColor disp 0)
  	(vla-put-LayoutCrosshairColor disp 16777215)
  	(vla-put-ModelCrosshairColor disp 16777215)
  	(vla-put-AutoTrackingVecColor disp 16777215)
  	(vla-put-AutoSnapMarkerColor drafting 2)
	)
	( (= MYCOLOR "WHITE") 
	(vl-load-com)
	(setenv "2D Model viewport control color" "0")
  	(setq disp (vla-get-display (vla-get-preferences (vlax-get-acad-object))))
  	(setq drafting (vla-get-drafting (vla-get-preferences (vlax-get-acad-object))))
  	(vla-put-GraphicsWinModelBackgrndColor disp 16777215)
  	(vla-put-GraphicsWinLayoutBackgrndColor disp 16777215)
  	(vla-put-LayoutCrosshairColor disp 0)
  	(vla-put-ModelCrosshairColor disp 0)
  	(vla-put-AutoTrackingVecColor disp 0)
  	(vla-put-AutoSnapMarkerColor drafting 2)
	)
	( (= MYCOLOR "GREY") 
	(vl-load-com)
	(setenv "2D Model viewport control color" "0")
  	(setq disp (vla-get-display (vla-get-preferences (vlax-get-acad-object))))
  	(setq drafting (vla-get-drafting (vla-get-preferences (vlax-get-acad-object))))
  	(vla-put-GraphicsWinModelBackgrndColor disp 4605510)
  	(vla-put-GraphicsWinLayoutBackgrndColor disp 4605510)
  	(vla-put-LayoutCrosshairColor disp 16777215)
  	(vla-put-ModelCrosshairColor disp 16777215)
  	(vla-put-AutoTrackingVecColor disp 16777215)
  	(vla-put-AutoSnapMarkerColor drafting 2)
	)
	)
   (princ)
  )
